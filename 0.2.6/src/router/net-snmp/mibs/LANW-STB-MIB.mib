--
-- LANW-STB-MIB.MIB
-- Tuesday, August 09, 2016 at 14:09:27
--

	LANW-STB-MIB DEFINITIONS ::= BEGIN
 
		IMPORTS
			OBJECT-GROUP			
				FROM SNMPv2-CONF			
			enterprises, TimeTicks, IpAddress, BITS, OBJECT-TYPE, 
			MODULE-IDENTITY, OBJECT-IDENTITY			
				FROM SNMPv2-SMI;
	
	
		-- 1.3.6.1.4.1.33898.1.1.1
		lwfstb MODULE-IDENTITY 
			LAST-UPDATED "201607241024Z"		-- July 24, 2016 at 10:24 GMT
			ORGANIZATION 
				"Organization."
			CONTACT-INFO 
				"Contact-info."
			DESCRIPTION 
				"Description."
			REVISION "201607241024Z"		-- July 24, 2016 at 10:24 GMT
			DESCRIPTION 
				"initialization import"
			::= { lwfModules 1 }

		
	
--
-- Node definitions
--
-- 1.3.6.1.4.1.33898
		lwfRoot OBJECT-IDENTITY
			STATUS current
			DESCRIPTION 
				"The root of the OID sub-tree assigned to Company by the Internet Assigned Numbers Authority (IANA)"
			::= { enterprises 33898 }

		
-- 1.3.6.1.4.1.33898.1
		lwfReg OBJECT-IDENTITY
			STATUS current
			DESCRIPTION 
				"Sub-tree for registrations"
			::= { lwfRoot 1 }

		
--   1.3.6.1.4.1.33898.1.1
		lwfModules OBJECT-IDENTITY
			STATUS current
			DESCRIPTION 
				"Sub-tree to register the values assigned to modules with the MODULE-IDENTITY construct"
			::= { lwfReg 1 }

		
--   1.3.6.1.4.1.33898.1.1.1.1
		lwfbasicsettings OBJECT-GROUP
			OBJECTS { lwfwifi0enable, lwfwifi0password, lwfwifi0ssid, lwfwifi0encryptionmethod, lwfwifi0keymanagement
				 }
			STATUS current
			DESCRIPTION 
				"Description."
			::= { lwfstb 1 }

		
-- 1.3.6.1.4.1.33898.1.1.1.2
		lwfwifi0enable OBJECT-TYPE
			SYNTAX INTEGER
				{
				enable(1),
				disable(2)
				}
			MAX-ACCESS read-write
			STATUS current
			DESCRIPTION
				"Description."
			::= { lwfstb 2 }

		
-- 1.3.6.1.4.1.33898.1.1.1.3
		lwfwifi0ssid OBJECT-TYPE
			SYNTAX OCTET STRING (SIZE (1..15))
			MAX-ACCESS read-write
			STATUS current
			DESCRIPTION
				"Description."
			::= { lwfstb 3 }

		
-- 1.3.6.1.4.1.33898.1.1.1.4
		lwfwifi0keymanagement OBJECT-TYPE
			SYNTAX BITS
				{
				wpapsk(0),
				wpa2psk(1)
				}
			MAX-ACCESS read-write
			STATUS current
			DESCRIPTION
				"Description."
			::= { lwfstb 4 }

		
-- 1.3.6.1.4.1.33898.1.1.1.5
		lwfwifi0encryptionmethod OBJECT-TYPE
			SYNTAX BITS
				{
				aes(0),
				tkipaes(1)
				}
			MAX-ACCESS read-write
			STATUS current
			DESCRIPTION
				"Description."
			::= { lwfstb 5 }

		
-- 1.3.6.1.4.1.33898.1.1.1.6
		lwfwifi0password OBJECT-TYPE
			SYNTAX OCTET STRING (SIZE (8..15))
			MAX-ACCESS read-write
			STATUS current
			DESCRIPTION
				"Description."
			::= { lwfstb 6 }

		
-- 1.3.6.1.4.1.33898.1.1.1.7
		flwfadvancedsettings OBJECT-GROUP
			OBJECTS { lwfwifi0phymode, lwfwifi0networkmode, lwfwifi0ssidbroadcast, lwfwifi0channel, lwfwifi0bandwidth, 
				wfwifi0txpower, lwfusername, lwfpassword, lwffactoryrestore, lwfreboot, 
				lwfapplysettings }
			STATUS current
			DESCRIPTION 
				"Description."
			::= { lwfstb 7 }

		
-- 1.3.6.1.4.1.33898.1.1.1.8
		lwfwifi0phymode OBJECT-TYPE
			SYNTAX INTEGER
				{
				abgn(1),
				ac(2)
				}
			MAX-ACCESS read-write
			STATUS current
			DESCRIPTION
				"Description."
			::= { lwfstb 8 }

		
-- 1.3.6.1.4.1.33898.1.1.1.9
		lwfwifi0networkmode OBJECT-TYPE
			SYNTAX INTEGER
				{
				router(1),
				bridge(2),
				ap(3),
				wds(4)
				}
			MAX-ACCESS read-write
			STATUS current
			DESCRIPTION
				"Description."
			::= { lwfstb 9 }

		
-- 1.3.6.1.4.1.33898.1.1.1.10
		lwfwifi0ssidbroadcast OBJECT-TYPE
			SYNTAX INTEGER
				{
				enable(1),
				disable(2)
				}
			MAX-ACCESS read-write
			STATUS current
			DESCRIPTION
				"Description."
			::= { lwfstb 10 }

		
-- 1.3.6.1.4.1.33898.1.1.1.11
		lwfwifi0channel OBJECT-TYPE
			SYNTAX INTEGER (1..13)
			MAX-ACCESS read-write
			STATUS current
			DESCRIPTION
				"Description."
			::= { lwfstb 11 }

		
-- 1.3.6.1.4.1.33898.1.1.1.12
		lwfwifi0bandwidth OBJECT-TYPE
			SYNTAX INTEGER
				{
				channel20M(1),
				channel40M(2)
				}
			MAX-ACCESS read-write
			STATUS current
			DESCRIPTION
				"Description."
			::= { lwfstb 12 }

		
-- 1.3.6.1.4.1.33898.1.1.1.14
		wfwifi0txpower OBJECT-TYPE
			SYNTAX INTEGER (1..100)
			MAX-ACCESS read-write
			STATUS current
			DESCRIPTION
				"Description."
			::= { lwfstb 14 }

		
-- 1.3.6.1.4.1.33898.1.1.1.15
		lwfusername OBJECT-TYPE
			SYNTAX OCTET STRING (SIZE (1..15))
			MAX-ACCESS read-write
			STATUS current
			DESCRIPTION
				"Description."
			::= { lwfstb 15 }

		
-- 1.3.6.1.4.1.33898.1.1.1.16
		lwfpassword OBJECT-TYPE
			SYNTAX OCTET STRING (SIZE (1..15))
			MAX-ACCESS read-write
			STATUS current
			DESCRIPTION
				"Description."
			::= { lwfstb 16 }

		
-- 1.3.6.1.4.1.33898.1.1.1.17
		lwffactoryrestore OBJECT-TYPE
			SYNTAX INTEGER { restore(1) }
			MAX-ACCESS read-write
			STATUS current
			DESCRIPTION
				"Description."
			::= { lwfstb 17 }

		
-- 1.3.6.1.4.1.33898.1.1.1.18
		lwfreboot OBJECT-TYPE
			SYNTAX INTEGER { reboot(1) }
			MAX-ACCESS read-write
			STATUS current
			DESCRIPTION
				"Description."
			::= { lwfstb 18 }

		
-- 1.3.6.1.4.1.33898.1.1.1.23
		lwfsupersettings OBJECT-GROUP
			OBJECTS { lwfsupersettingsenable, lwfssidmodifyenable, lwfwifi0ssidheader, lwfwifi1ssid }
			STATUS current
			DESCRIPTION 
				"Description."
			::= { lwfstb 23 }

		
-- 1.3.6.1.4.1.33898.1.1.1.26
		lwfsupersettingsenable OBJECT-TYPE
			SYNTAX INTEGER
				{
				enable(1),
				disable(2)
				}
			MAX-ACCESS read-write
			STATUS current
			DESCRIPTION
				"Description."
			::= { lwfstb 26 }

		
-- 1.3.6.1.4.1.33898.1.1.1.27
		lwfssidmodifyenable OBJECT-TYPE
			SYNTAX INTEGER
				{
				enable(1),
				disable(2)
				}
			MAX-ACCESS read-write
			STATUS current
			DESCRIPTION
				"Description."
			::= { lwfstb 27 }

		
-- 1.3.6.1.4.1.33898.1.1.1.28
		lwfwifi0ssidheader OBJECT-TYPE
			SYNTAX OCTET STRING (SIZE (1..8))
			MAX-ACCESS read-write
			STATUS current
			DESCRIPTION
				"Description."
			::= { lwfstb 28 }

		
-- 1.3.6.1.4.1.33898.1.1.1.29
		lwfwifi1ssid OBJECT-TYPE
			SYNTAX OCTET STRING (SIZE (1..15))
			MAX-ACCESS read-write
			STATUS current
			DESCRIPTION
				"Description."
			::= { lwfstb 29 }

		
-- 1.3.6.1.4.1.33898.1.1.1.30
		lwfstatus OBJECT-GROUP
			OBJECTS { lwfwifi0mac, lwflanmac, lwfwanlink, lwfwanip, lwfwanmask, 
				clientmac, clientindex, lwfwandns2, lwfwandns1, lwflanip, 
				lwflanmask, clientip, clientleasetime, stationindex, stationmac, 
				assoctime }
			STATUS current
			DESCRIPTION 
				"Description."
			::= { lwfstb 30 }

		
-- 1.3.6.1.4.1.33898.1.1.1.31
		lwfwifi0mac OBJECT-TYPE
			SYNTAX OCTET STRING (SIZE (17))
			MAX-ACCESS read-only
			STATUS current
			DESCRIPTION
				"Description."
			::= { lwfstb 31 }

		
-- 1.3.6.1.4.1.33898.1.1.1.33
		lwfwanlink OBJECT-TYPE
			SYNTAX INTEGER
				{
				dhcpok(1),
				dhcpnok(2)
				}
			MAX-ACCESS read-only
			STATUS current
			DESCRIPTION
				"Description."
			::= { lwfstb 33 }

		
-- 1.3.6.1.4.1.33898.1.1.1.34
		lwfwanip OBJECT-TYPE
			SYNTAX IpAddress
			MAX-ACCESS read-only
			STATUS current
			DESCRIPTION
				"Description."
			::= { lwfstb 34 }

		
-- 1.3.6.1.4.1.33898.1.1.1.35
		lwfwanmask OBJECT-TYPE
			SYNTAX IpAddress
			MAX-ACCESS read-only
			STATUS current
			DESCRIPTION
				"Description."
			::= { lwfstb 35 }

		
-- 1.3.6.1.4.1.33898.1.1.1.36
		lwfwandns1 OBJECT-TYPE
			SYNTAX IpAddress
			MAX-ACCESS read-only
			STATUS current
			DESCRIPTION
				"Description."
			::= { lwfstb 36 }

		
-- 1.3.6.1.4.1.33898.1.1.1.37
		lwfwandns2 OBJECT-TYPE
			SYNTAX IpAddress
			MAX-ACCESS read-only
			STATUS current
			DESCRIPTION
				"Description."
			::= { lwfstb 37 }

		
-- 1.3.6.1.4.1.33898.1.1.1.38
		lwflanmac OBJECT-TYPE
			SYNTAX OCTET STRING (SIZE (17))
			MAX-ACCESS read-only
			STATUS current
			DESCRIPTION
				"Description."
			::= { lwfstb 38 }

		
-- 1.3.6.1.4.1.33898.1.1.1.39
		lwflanip OBJECT-TYPE
			SYNTAX IpAddress
			MAX-ACCESS read-only
			STATUS current
			DESCRIPTION
				"Description."
			::= { lwfstb 39 }

		
-- 1.3.6.1.4.1.33898.1.1.1.40
		lwflanmask OBJECT-TYPE
			SYNTAX IpAddress
			MAX-ACCESS read-only
			STATUS current
			DESCRIPTION
				"Description."
			::= { lwfstb 40 }

		
-- 1.3.6.1.4.1.33898.1.1.1.41
		lwfwpssettings OBJECT-GROUP
			OBJECTS { lwfwifi0wpsenable, lwfwifi0wpsstart, lwfwifi0wpsstatus, lwfwifi0wpspin }
			STATUS current
			DESCRIPTION 
				"Description."
			::= { lwfstb 41 }

		
-- 1.3.6.1.4.1.33898.1.1.1.42
		lwfwifi0wpsenable OBJECT-TYPE
			SYNTAX INTEGER
				{
				enable(1),
				disable(2)
				}
			MAX-ACCESS read-write
			STATUS current
			DESCRIPTION
				"Description."
			::= { lwfstb 42 }

		
-- 1.3.6.1.4.1.33898.1.1.1.43
		lwfwifi0wpspin OBJECT-TYPE
			SYNTAX OCTET STRING (SIZE (8))
			MAX-ACCESS read-write
			STATUS current
			DESCRIPTION
				"Description."
			::= { lwfstb 43 }

		
-- 1.3.6.1.4.1.33898.1.1.1.44
		lwfwifi0wpsstart OBJECT-TYPE
			SYNTAX INTEGER
				{
				start(1),
				stop(2)
				}
			MAX-ACCESS read-write
			STATUS current
			DESCRIPTION
				"Description."
			::= { lwfstb 44 }

		
-- 1.3.6.1.4.1.33898.1.1.1.45
		lwfwifi0wpsstatus OBJECT-TYPE
			SYNTAX INTEGER
				{
				inactive(1),
				inprogress(2),
				success(3)
				}
			MAX-ACCESS read-only
			STATUS current
			DESCRIPTION
				"Description."
			::= { lwfstb 45 }

		
-- 1.3.6.1.4.1.33898.1.1.1.46
		lwfwdssettings OBJECT-GROUP
			OBJECTS { lwfwifi0wdsremotemac }
			STATUS current
			DESCRIPTION 
				"Description."
			::= { lwfstb 46 }

		
-- 1.3.6.1.4.1.33898.1.1.1.47
		lwfwifi0wdsremotemac OBJECT-TYPE
			SYNTAX OCTET STRING (SIZE (15))
			MAX-ACCESS read-write
			STATUS current
			DESCRIPTION
				"Description."
			::= { lwfstb 47 }

		
-- 1.3.6.1.4.1.33898.1.1.1.48
		dhcpclientTable OBJECT-TYPE
			SYNTAX SEQUENCE OF DhcpclientEntry
			MAX-ACCESS not-accessible
			STATUS current
			DESCRIPTION
				"Description."
			::= { lwfstb 48 }

		
-- 1.3.6.1.4.1.33898.1.1.1.48.1
		dhcpclientEntry OBJECT-TYPE
			SYNTAX DhcpclientEntry
			MAX-ACCESS not-accessible
			STATUS current
			DESCRIPTION
				"Description."
			INDEX { clientindex }
			::= { dhcpclientTable 1 }

		
		DhcpclientEntry ::=
			SEQUENCE { 
				clientindex
					INTEGER,
				clientmac
					OCTET STRING,
				clientip
					IpAddress,
				clientleasetime
					TimeTicks
			 }

-- 1.3.6.1.4.1.33898.1.1.1.48.1.1
		clientindex OBJECT-TYPE
			SYNTAX INTEGER (1..200)
			MAX-ACCESS read-only
			STATUS current
			DESCRIPTION
				"Description."
			::= { dhcpclientEntry 1 }

		
-- 1.3.6.1.4.1.33898.1.1.1.48.1.2
		clientmac OBJECT-TYPE
			SYNTAX OCTET STRING (SIZE (18))
			MAX-ACCESS read-only
			STATUS current
			DESCRIPTION
				"Description."
			::= { dhcpclientEntry 2 }

		
-- 1.3.6.1.4.1.33898.1.1.1.48.1.3
		clientip OBJECT-TYPE
			SYNTAX IpAddress
			MAX-ACCESS read-only
			STATUS current
			DESCRIPTION
				"Description."
			::= { dhcpclientEntry 3 }

		
-- 1.3.6.1.4.1.33898.1.1.1.48.1.4
		clientleasetime OBJECT-TYPE
			SYNTAX TimeTicks
			MAX-ACCESS read-only
			STATUS current
			DESCRIPTION
				"Description."
			::= { dhcpclientEntry 4 }

		
-- 1.3.6.1.4.1.33898.1.1.1.49
		wifistationTable OBJECT-TYPE
			SYNTAX SEQUENCE OF WifistationEntry
			MAX-ACCESS not-accessible
			STATUS current
			DESCRIPTION
				"Description."
			::= { lwfstb 49 }

		
-- 1.3.6.1.4.1.33898.1.1.1.49.1
		wifistationEntry OBJECT-TYPE
			SYNTAX WifistationEntry
			MAX-ACCESS not-accessible
			STATUS current
			DESCRIPTION
				"Description."
			INDEX { stationindex }
			::= { wifistationTable 1 }

		
		WifistationEntry ::=
			SEQUENCE { 
				stationindex
					INTEGER,
				stationmac
					OCTET STRING,
				assoctime
					TimeTicks
			 }

-- 1.3.6.1.4.1.33898.1.1.1.49.1.1
		stationindex OBJECT-TYPE
			SYNTAX INTEGER (1..32)
			MAX-ACCESS read-only
			STATUS current
			DESCRIPTION
				"Description."
			::= { wifistationEntry 1 }

		
-- 1.3.6.1.4.1.33898.1.1.1.49.1.2
		stationmac OBJECT-TYPE
			SYNTAX OCTET STRING (SIZE (18))
			MAX-ACCESS read-only
			STATUS current
			DESCRIPTION
				"Description."
			::= { wifistationEntry 2 }

		
-- 1.3.6.1.4.1.33898.1.1.1.49.1.3
		assoctime OBJECT-TYPE
			SYNTAX TimeTicks
			MAX-ACCESS read-only
			STATUS current
			DESCRIPTION
				"Description."
			::= { wifistationEntry 3 }

		
-- 1.3.6.1.4.1.33898.1.1.1.50
		lwfapplysettings OBJECT-TYPE
			SYNTAX INTEGER { enable(1) }
			MAX-ACCESS read-write
			STATUS current
			DESCRIPTION
				"Description."
			::= { lwfstb 50 }

		
-- 1.3.6.1.4.1.33898.2
		lwfGeneric OBJECT-IDENTITY
			STATUS current
			DESCRIPTION 
				"Sub-tree for common object and event definitions"
			::= { lwfRoot 2 }

		
-- 1.3.6.1.4.1.33898.3
		lwfProducts OBJECT-IDENTITY
			STATUS current
			DESCRIPTION 
				"Sub-tree for specific object and event definitions"
			::= { lwfRoot 3 }

		
-- 1.3.6.1.4.1.33898.4
		lwfCaps OBJECT-IDENTITY
			STATUS current
			DESCRIPTION 
				"Sub-tree for agent profiles"
			::= { lwfRoot 4 }

		
-- 1.3.6.1.4.1.33898.5
		lwfReqs OBJECT-IDENTITY
			STATUS current
			DESCRIPTION 
				"Sub-tree for management application requirements"
			::= { lwfRoot 5 }

		
-- 1.3.6.1.4.1.33898.6
		lwfExpr OBJECT-IDENTITY
			STATUS current
			DESCRIPTION 
				"Sub-tree for experimental definitions"
			::= { lwfRoot 6 }

		
	
	END

--
-- LANW-STB-MIB.MIB
--
